# Requisitos_NASH_Planta_MCP_ER_Prop_V1e_

## Requisitos_NASH_Planta_MCP_ER_Prop_V1e_!MCP_reqs: References to Requisitos_NASH_Planta_MCP_ER_Prop_V1e_.xlsx (MCP_reqs) (Container)
Read-only references to Microsoft Excel document.

### 001-F-MCP-001: O modelo do MCP deve representar dinamicamente as variáveis lidas pelo IPMS. (Functional)

### 001-F-MCP-002: O modelo do MCP deve receber estímulo de sinal vindo do IPMS. (Functional)

### 001-F-MCP-003: No estado do motor desligado, o modelo do MCP deve ignorar comandos de demanda de rotação. (Functional)

### 001-F-MCP-004: No estado de motor parado, o modelo do MCP deve representar o valor de rotação igual a 0 RPM. (Functional)

### 001-F-MCP-005: Quando em ralenti, o modelo do MCP deve representar o valor de rotação igual a 600 RPM. (Functional)

### 001-F-MCP-006: No estado de motor rodando, o modelo do MCP deve representar a dinâmica de rotação do motor de acordo com a demanda e com o estado da engrenagem reversora. (Functional)

### 001-F-MCP-007: A dinâmida de rotação do modelo do MCP deve apresentar o comportamento do motor representado no EST-156. (Functional)

### 001-F-MCP-008: Por meio da IHM do simulador, o modelo do MCP deve permitir a inserção de falhas pelo operador do sistema. (Functional)

### 001-F-MCP-008-1: Por meio da IHM do simulador, o modelo do MCP deve permitir a inserção de falha pressão de boost diferente de zero. (Functional)

### 001-F-MCP-008-2: Por meio da IHM do simulador, o modelo do MCP deve permitir a inserção de falha temperatura de exaustão fora da faixa de operação normal. (Functional)

### 001-F-MCP-008-3: Por meio da IHM do simulador, o modelo do MCP deve permitir a inserção de falha do sinal de rotação do MCP. (Functional)

### 001-F-MCP-008-4: Por meio da IHM do simulador, o modelo do MCP deve permitir a inserção de falha de pressão de óleo lubrificante. (Functional)

### 001-F-MCP-008-5: Por meio da IHM do simulador, o modelo do MCP deve permitir a inserção de falha de temperatura de água de resfriamento. (Functional)

### 001-F-MCP-008-6: Por meio da IHM do simulador, o modelo do MCP deve permitir a inserção de falha de pressão de ar. (Functional)

### 001-F-MCP-009: Os valores dos sinais de temperatura de exaustão (MCPBE0.21 a 26) devem possuir dinâmica linear de 1a ordem baseada nos dados do IPQM-REL-156. (Functional)

### 001-F-MCP-010: O modelo do MCP deve representar o consumo instantaneo de combustível em L/h de acordo com a figura D.1. do EST-270. (Functional)

### 001-F-MCP-011: O modelo do MCP deve representar a potência do motor em kW de acordo com a figura D.1 do EST-270. (Functional)

### 001-F-MCP-012: A geração dos valores da potência de saída do modelo deve considerar valores em regime estático (sistema elástico). (Functional)

### 001-F-MCP-013: O torque calculado no modelo do motor (MCPBE1.3) deve ser um sinal de saída do modelo do MCP para a engrenagem reversora. (Functional)

### 001-F-MCP-014: As saídas referentes aos alarmes devem basear-se nos valores disponíveis em (YANMAR, 2003) (Functional)

### 001-F-MCP-015: Quando virando, o modelo deve representar a dinâmica do motor entre 600 e 2000 rpm, conforme detalhado no IPQM-REL-156. (Functional)

### 001-F-MCP-016: O comportamento do sinal da temperatura da água de resfriamento(MCPBE0.19) deve ser implementado por uma TF de primeira ordem de regime estacionário entre Tambiente e 90°C de acordo com dados do EST-270. (Functional)

### 001-F-MCP-017: O sinal simulado de pressão de boost (MCPBE0.20) do MCPBE deve ser um sinal constante (0 MPa em unidade de engenharia), de acordo com YANMAR,2003. (Functional)

## #25: Justifications

### #26: Inserção de falha boost
Implementado o "modelo model_mcp_boost_pressure" que, além da saída em situação igual a zero prevê também a inserção de falha através da variável "sp_vl_boost_error==1", tornando a saída diferente de zero.

### #27: Demanda zero no estado off do mcp
Dentro do estado OFF do stateChart "state_mcp_gear" a variável "out_va_mcp_rpm_demand =0" garante que no estado desligado do motor a demanda será sempre sobrescrita e igual a zero.

### #28: ralenti 600 RPM
De acordo com a lookup table "demand_to_rpm", a menor demanda irá garantir uma rotação de 600 RPM.

### #29: dinâmica rotação
Dentro do stateChart "state_mcp_gear", há um super estado que realização a mudança paramétrica da função de transferência "tf_mcp_rotation", responsável por representar a dinâmica de rotação do MCP.

### #30: Implementação na IHM
Falhas que serão implementadas por meio da IHM do simulador.

### #31: Dinâmica Temp Exaustão
A dinâmica de temperatura de exaustão é implementada pelo modelo tf_exhaust_cil_temp, obedecendo o modelo de primeira ordem.

### #32: Consumo combustível l/h
A implementação é realizada por meio da Lookup Table "fuel consumption".

### #33: Potência MCP
A implementação é realizada por meio da Lookup Table "rpm_to_power".

### #35: Saída Torque
Está prevista uma variável para a ER: "pp_mcp_torque".

### #36: RPM Min e Max
As variáveis "mcp_nominal_rotation" e "mcp_ralenti_rotation" são responsáveis por limitar as rotações mínima e máxima de operação do motor.

### #37: dinâmica Temp Água Resfr
O modelo "tf_cooling_water" possui a dinâmica da temperatura de água de resfriamento e está limitada pelas variáveis "ambient_temp" e "mcp_max_cooling_water_temp".

### #38: Pressão de Boost
O modelo "model_mcp_boost_pressure" implementa a pressão do boost para que, em condições normais, a saída seja igual a 0.

### #39: Interface MCP
Foram implementadas as entradas e saídas previstas no DFD, anexo do EST-270.
